"""Bulk-convert IGES files to STEP files.

Each selected IGES file is read as a single shape, moved so that the minimum
corner of its exact bounding box sits at the origin, and written to a `stepout`
folder next to the source file.

The move is baked into the geometry. It is deliberately not applied as an
object Placement and the shape is not wrapped in a group, because that makes
the exported STEP a nested assembly (a parent product plus an
ITEM_DEFINED_TRANSFORMATION offset), which some importers, such as Bend-Tech
DragonCAM, fail to read.
"""

import os
from typing import Final

import FreeCAD
import Part
from PySide import QtWidgets

OUTPUT_FOLDER_NAME: Final = "stepout"
DIALOG_TITLE: Final = "Select IGES Files"
IGES_FILTER: Final = "IGES files (*.igs *.iges)"


def select_iges_files() -> list[str]:
    paths, _selected_filter = QtWidgets.QFileDialog.getOpenFileNames(
        None, DIALOG_TITLE, "", IGES_FILTER
    )
    return paths


def convert(iges_path: str) -> str:
    """Convert one IGES file and return the path of the STEP file written."""
    output_dir = os.path.join(os.path.dirname(iges_path), OUTPUT_FOLDER_NAME)
    os.makedirs(output_dir, exist_ok=True)
    step_path = os.path.join(
        output_dir, os.path.splitext(os.path.basename(iges_path))[0] + ".step"
    )

    shape = Part.read(iges_path)
    if shape.isNull():
        raise ValueError("no geometry found in file")

    # The exact (non-tolerance-padded) box puts the part on the origin to within
    # floating-point error; Shape.BoundBox is padded by the shape tolerance.
    bbox = shape.optimalBoundingBox(False, False)
    matrix = FreeCAD.Matrix()
    matrix.move(FreeCAD.Vector(-bbox.XMin, -bbox.YMin, -bbox.ZMin))

    # copy=True rewrites the geometry itself. copy=False would only attach a
    # location to the shape, which is the thing that must not reach the STEP.
    shape.transformShape(matrix, True)

    shape.exportStep(step_path)
    return step_path


def main() -> None:
    iges_paths = select_iges_files()
    if not iges_paths:
        print("No IGES files selected.")
        return

    failed: list[str] = []
    for iges_path in iges_paths:
        try:
            print(f"Exported: {convert(iges_path)}")
        except Exception as error:
            failed.append(iges_path)
            print(f"FAILED: {os.path.basename(iges_path)}: {error}")

    print(f"Done: {len(iges_paths) - len(failed)} converted, {len(failed)} failed.")


main()
